# NIST_SP_800_171R2
Generated by Loop APIs v10

# Specification: NIST_SP_800_171R2

## R1: ACCESS CONTROL (Info)
- ChapterNumber: 3.1
- Level: 2

### 3.1.1 (Requirement)
3.1.1
Limit system access to authorized users, processes acting on behalf of authorized users, and devices (including other systems).
- ChapterNumber: 3.1 ACCESS CONTROL
- Source File: NIST_SP_800-171r2.pdf
- Coverage: AVAILABLE

### 3.1.2 (Requirement)
3.1.2
Limit system access to the types of transactions and functions that authorized users are permitted to execute.
- ChapterNumber: 3.1 ACCESS CONTROL
- Source File: NIST_SP_800-171r2.pdf
- Coverage: AVAILABLE

### 3.1.3 (Requirement)
3.1.3
Control the flow of CUI in accordance with approved authorizations.
- ChapterNumber: 3.1 ACCESS CONTROL
- Source File: NIST_SP_800-171r2.pdf
- Coverage: AVAILABLE

### 3.1.4 (Requirement)
3.1.4
Separate the duties of individuals to reduce the risk of malevolent activity without collusion.
- ChapterNumber: 3.1 ACCESS CONTROL
- Source File: NIST_SP_800-171r2.pdf
- Coverage: AVAILABLE

### 3.1.5 (Requirement)
3.1.5
Employ the principle of least privilege, including for specific security functions and privileged accounts.
- ChapterNumber: 3.1 ACCESS CONTROL
- Source File: NIST_SP_800-171r2.pdf
- Coverage: AVAILABLE

### 3.1.6 (Requirement)
3.1.6
Use non-privileged accounts or roles when accessing nonsecurity functions.
- ChapterNumber: 3.1 ACCESS CONTROL
- Source File: NIST_SP_800-171r2.pdf
- Coverage: AVAILABLE

### 3.1.7 (Requirement)
3.1.7
Prevent non-privileged users from executing privileged functions and capture the execution of such functions in audit logs.
- ChapterNumber: 3.1 ACCESS CONTROL
- Source File: NIST_SP_800-171r2.pdf
- Coverage: AVAILABLE

### 3.1.8 (Requirement)
3.1.8
Limit unsuccessful logon attempts.
- ChapterNumber: 3.1 ACCESS CONTROL
- Source File: NIST_SP_800-171r2.pdf
- Coverage: AVAILABLE

### 3.1.9 (Requirement)
3.1.9
Provide privacy and security notices consistent with applicable CUI rules.
- ChapterNumber: 3.1 ACCESS CONTROL
- Source File: NIST_SP_800-171r2.pdf
- Coverage: AVAILABLE

### 3.1.10 (Requirement)
3.1.10
Use session lock with pattern-hiding displays to prevent access and viewing of data after a period of inactivity.
- ChapterNumber: 3.1 ACCESS CONTROL
- Source File: NIST_SP_800-171r2.pdf
- Coverage: AVAILABLE

### 3.1.11 (Requirement)
3.1.11
Terminate (automatically) a user session after a defined condition.
- ChapterNumber: 3.1 ACCESS CONTROL
- Source File: NIST_SP_800-171r2.pdf
- Coverage: AVAILABLE

### 3.1.12 (Requirement)
3.1.12
Monitor and control remote access sessions.
- ChapterNumber: 3.1 ACCESS CONTROL
- Source File: NIST_SP_800-171r2.pdf
- Coverage: AVAILABLE

### 3.1.13 (Requirement)
3.1.13
Employ cryptographic mechanisms to protect the confidentiality of remote access sessions.
- ChapterNumber: 3.1 ACCESS CONTROL
- Source File: NIST_SP_800-171r2.pdf
- Coverage: AVAILABLE

### 3.1.14 (Requirement)
3.1.14
Route remote access via managed access control points.
- ChapterNumber: 3.1 ACCESS CONTROL
- Source File: NIST_SP_800-171r2.pdf
- Coverage: AVAILABLE

### 3.1.15 (Requirement)
3.1.15
Authorize remote execution of privileged commands and remote access to security-relevant information.
- ChapterNumber: 3.1 ACCESS CONTROL
- Source File: NIST_SP_800-171r2.pdf
- Coverage: AVAILABLE

### 3.1.16 (Requirement)
3.1.16
Authorize wireless access prior to allowing such connections.
- ChapterNumber: 3.1 ACCESS CONTROL
- Source File: NIST_SP_800-171r2.pdf
- Coverage: AVAILABLE

### 3.1.17 (Requirement)
3.1.17
Protect wireless access using authentication and encryption.
- ChapterNumber: 3.1 ACCESS CONTROL
- Source File: NIST_SP_800-171r2.pdf
- Coverage: AVAILABLE

### 3.1.18 (Requirement)
3.1.18
Control connection of mobile devices.
- ChapterNumber: 3.1 ACCESS CONTROL
- Source File: NIST_SP_800-171r2.pdf
- Coverage: AVAILABLE

### 3.1.19 (Requirement)
3.1.19
Encrypt CUI on mobile devices and mobile computing platforms. 23
- ChapterNumber: 3.1 ACCESS CONTROL
- Source File: NIST_SP_800-171r2.pdf
- Coverage: AVAILABLE

### 3.1.20 (Requirement)
3.1.20
Verify and control/limit connections to and use of external systems.
- ChapterNumber: 3.1 ACCESS CONTROL
- Source File: NIST_SP_800-171r2.pdf
- Coverage: AVAILABLE

### 3.1.21 (Requirement)
3.1.21
Limit use of portable storage devices on external systems.
- ChapterNumber: 3.1 ACCESS CONTROL
- Source File: NIST_SP_800-171r2.pdf
- Coverage: AVAILABLE

### 3.1.22 (Requirement)
3.1.22
Control CUI posted or processed on publicly accessible systems.
- ChapterNumber: 3.1 ACCESS CONTROL
- Source File: NIST_SP_800-171r2.pdf
- Coverage: AVAILABLE

## R2: AWARENESS AND TRAINING (Info)
- ChapterNumber: 3.2
- Level: 2

### 3.2.1 (Requirement)
3.2.1
Ensure that managers, systems administrators, and users of organizational systems are made aware of the security risks associated with their activities and of the applicable policies, standards, and procedures related to the security of those systems.
- ChapterNumber: 3.2 AWARENESS AND TRAINING
- Source File: NIST_SP_800-171r2.pdf
- Coverage: AVAILABLE

### 3.2.2 (Requirement)
3.2.2
Ensure that personnel are trained to carry out their assigned information security-related duties and responsibilities.
- ChapterNumber: 3.2 AWARENESS AND TRAINING
- Source File: NIST_SP_800-171r2.pdf
- Coverage: AVAILABLE

### 3.2.3 (Requirement)
3.2.3
Provide security awareness training on recognizing and reporting potential indicators of insider threat.
- ChapterNumber: 3.2 AWARENESS AND TRAINING
- Source File: NIST_SP_800-171r2.pdf
- Coverage: AVAILABLE

## R3: AUDIT AND ACCOUNTABILITY (Info)
- ChapterNumber: 3.3
- Level: 2

### 3.3.1 (Requirement)
3.3.1
Create and retain system audit logs and records to the extent needed to enable the monitoring, analysis, investigation, and reporting of unlawful or unauthorized system activity.
- ChapterNumber: 3.3 AUDIT AND ACCOUNTABILITY
- Source File: NIST_SP_800-171r2.pdf
- Coverage: AVAILABLE

### 3.3.2 (Requirement)
3.3.2
Ensure that the actions of individual system users can be uniquely traced to those users, so they can be held accountable for their actions.
- ChapterNumber: 3.3 AUDIT AND ACCOUNTABILITY
- Source File: NIST_SP_800-171r2.pdf
- Coverage: AVAILABLE

### 3.3.3 (Requirement)
3.3.3
Review and update logged events.
- ChapterNumber: 3.3 AUDIT AND ACCOUNTABILITY
- Source File: NIST_SP_800-171r2.pdf
- Coverage: AVAILABLE

### 3.3.4 (Requirement)
3.3.4
Alert in the event of an audit logging process failure.
- ChapterNumber: 3.3 AUDIT AND ACCOUNTABILITY
- Source File: NIST_SP_800-171r2.pdf
- Coverage: AVAILABLE

### 3.3.5 (Requirement)
3.3.5
Correlate audit record review, analysis, and reporting processes for investigation and response to indications of unlawful, unauthorized, suspicious, or unusual activity.
- ChapterNumber: 3.3 AUDIT AND ACCOUNTABILITY
- Source File: NIST_SP_800-171r2.pdf
- Coverage: AVAILABLE

### 3.3.6 (Requirement)
3.3.6
Provide audit record reduction and report generation to support on-demand analysis and reporting.
- ChapterNumber: 3.3 AUDIT AND ACCOUNTABILITY
- Source File: NIST_SP_800-171r2.pdf
- Coverage: AVAILABLE

### 3.3.7 (Requirement)
3.3.7
Provide a system capability that compares and synchronizes internal system clocks with an authoritative source to generate time stamps for audit records.
- ChapterNumber: 3.3 AUDIT AND ACCOUNTABILITY
- Source File: NIST_SP_800-171r2.pdf
- Coverage: AVAILABLE

### 3.3.8 (Requirement)
3.3.8
Protect audit information and audit logging tools from unauthorized access, modification, and deletion.
- ChapterNumber: 3.3 AUDIT AND ACCOUNTABILITY
- Source File: NIST_SP_800-171r2.pdf
- Coverage: AVAILABLE

### 3.3.9 (Requirement)
3.3.9
Limit management of audit logging functionality to a subset of privileged users.
- ChapterNumber: 3.3 AUDIT AND ACCOUNTABILITY
- Source File: NIST_SP_800-171r2.pdf
- Coverage: AVAILABLE

## R4: CONFIGURATION MANAGEMENT (Info)
- ChapterNumber: 3.4
- Level: 2

### 3.4.1 (Requirement)
3.4.1
Establish and maintain baseline configurations and inventories of organizational systems (including hardware, software, firmware, and documentation) throughout the respective system development life cycles.
- ChapterNumber: 3.4 CONFIGURATION MANAGEMENT
- Source File: NIST_SP_800-171r2.pdf
- Coverage: AVAILABLE

### 3.4.2 (Requirement)
3.4.2
Establish and enforce security configuration settings for information technology products employed in organizational systems.
- ChapterNumber: 3.4 CONFIGURATION MANAGEMENT
- Source File: NIST_SP_800-171r2.pdf
- Coverage: AVAILABLE

### 3.4.3 (Requirement)
3.4.3
Track, review, approve or disapprove, and log changes to organizational systems.
- ChapterNumber: 3.4 CONFIGURATION MANAGEMENT
- Source File: NIST_SP_800-171r2.pdf
- Coverage: AVAILABLE

### 3.4.4 (Requirement)
3.4.4
Analyze the security impact of changes prior to implementation.
- ChapterNumber: 3.4 CONFIGURATION MANAGEMENT
- Source File: NIST_SP_800-171r2.pdf
- Coverage: AVAILABLE

### 3.4.5 (Requirement)
3.4.5
Define, document, approve, and enforce physical and logical access restrictions associated with changes to organizational systems.
- ChapterNumber: 3.4 CONFIGURATION MANAGEMENT
- Source File: NIST_SP_800-171r2.pdf
- Coverage: AVAILABLE

### 3.4.6 (Requirement)
3.4.6
Employ the principle of least functionality by configuring organizational systems to provide only essential capabilities.
- ChapterNumber: 3.4 CONFIGURATION MANAGEMENT
- Source File: NIST_SP_800-171r2.pdf
- Coverage: AVAILABLE

### 3.4.7 (Requirement)
3.4.7
Restrict, disable, or prevent the use of nonessential programs, functions, ports, protocols, and services.
- ChapterNumber: 3.4 CONFIGURATION MANAGEMENT
- Source File: NIST_SP_800-171r2.pdf
- Coverage: AVAILABLE

### 3.4.8 (Requirement)
3.4.8
Apply deny-by-exception (blacklisting) policy to prevent the use of unauthorized software or deny-all, permit-by-exception (whitelisting) policy to allow the execution of authorized software.
- ChapterNumber: 3.4 CONFIGURATION MANAGEMENT
- Source File: NIST_SP_800-171r2.pdf
- Coverage: AVAILABLE

### 3.4.9 (Requirement)
3.4.9
Control and monitor user-installed software.
- ChapterNumber: 3.4 CONFIGURATION MANAGEMENT
- Source File: NIST_SP_800-171r2.pdf
- Coverage: AVAILABLE

## R5: IDENTIFICATION AND AUTHENTICATION (Info)
- ChapterNumber: 3.5
- Level: 2

### 3.5.1 (Requirement)
3.5.1
Identify system users, processes acting on behalf of users, and devices.
- ChapterNumber: 3.5 IDENTIFICATION AND AUTHENTICATION
- Source File: NIST_SP_800-171r2.pdf
- Coverage: AVAILABLE

### 3.5.2 (Requirement)
3.5.2
Authenticate (or verify) the identities of users, processes, or devices, as a prerequisite to allowing access to organizational systems.
- ChapterNumber: 3.5 IDENTIFICATION AND AUTHENTICATION
- Source File: NIST_SP_800-171r2.pdf
- Coverage: AVAILABLE

### 3.5.3 (Requirement)
3.5.3
Use multifactor authentication for local and network access to privileged accounts and for network access to non-privileged accounts. 24 25
- ChapterNumber: 3.5 IDENTIFICATION AND AUTHENTICATION
- Source File: NIST_SP_800-171r2.pdf
- Coverage: AVAILABLE

### 3.5.4 (Requirement)
3.5.4
Employ replay-resistant authentication mechanisms for network access to privileged and nonprivileged accounts.
- ChapterNumber: 3.5 IDENTIFICATION AND AUTHENTICATION
- Source File: NIST_SP_800-171r2.pdf
- Coverage: AVAILABLE

### 3.5.5 (Requirement)
3.5.5
Prevent reuse of identifiers for a defined period.
- ChapterNumber: 3.5 IDENTIFICATION AND AUTHENTICATION
- Source File: NIST_SP_800-171r2.pdf
- Coverage: AVAILABLE

### 3.5.6 (Requirement)
3.5.6
Disable identifiers after a defined period of inactivity.
- ChapterNumber: 3.5 IDENTIFICATION AND AUTHENTICATION
- Source File: NIST_SP_800-171r2.pdf
- Coverage: AVAILABLE

### 3.5.7 (Requirement)
3.5.7
Enforce a minimum password complexity and change of characters when new passwords are created .
- ChapterNumber: 3.5 IDENTIFICATION AND AUTHENTICATION
- Source File: NIST_SP_800-171r2.pdf
- Coverage: AVAILABLE

### 3.5.8 (Requirement)
3.5.8
Prohibit password reuse for a specified number of generations.
- ChapterNumber: 3.5 IDENTIFICATION AND AUTHENTICATION
- Source File: NIST_SP_800-171r2.pdf
- Coverage: AVAILABLE

### 3.5.9 (Requirement)
3.5.9
Allow temporary password use for system logons with an immediate change to a permanent password.
- ChapterNumber: 3.5 IDENTIFICATION AND AUTHENTICATION
- Source File: NIST_SP_800-171r2.pdf
- Coverage: AVAILABLE

### 3.5.10 (Requirement)
3.5.10
Store and transmit only cryptographically-protected passwords.
- ChapterNumber: 3.5 IDENTIFICATION AND AUTHENTICATION
- Source File: NIST_SP_800-171r2.pdf
- Coverage: AVAILABLE

### 3.5.11 (Requirement)
3.5.11
Obscure feedback of authentication information.
- ChapterNumber: 3.5 IDENTIFICATION AND AUTHENTICATION
- Source File: NIST_SP_800-171r2.pdf
- Coverage: AVAILABLE

## R6: INCIDENT RESPONSE (Info)
- ChapterNumber: 3.6
- Level: 2

### 3.6.1 (Requirement)
3.6.1
Establish an operational incident-handling capability for organizational systems that includes preparation, detection, analysis, containment, recovery, and user response activities.
- ChapterNumber: 3.6 INCIDENT RESPONSE
- Source File: NIST_SP_800-171r2.pdf
- Coverage: AVAILABLE

### 3.6.2 (Requirement)
3.6.2
Track, document, and report incidents to designated officials and/or authorities both internal and external to the organization.
- ChapterNumber: 3.6 INCIDENT RESPONSE
- Source File: NIST_SP_800-171r2.pdf
- Coverage: AVAILABLE

### 3.6.3 (Requirement)
3.6.3
Test the organizational incident response capability.
- ChapterNumber: 3.6 INCIDENT RESPONSE
- Source File: NIST_SP_800-171r2.pdf
- Coverage: AVAILABLE

## R7: MAINTENANCE (Info)
- ChapterNumber: 3.7
- Level: 2

### 3.7.1 (Requirement)
3.7.1
Perform maintenance on organizational systems. 26
- ChapterNumber: 3.7 MAINTENANCE
- Source File: NIST_SP_800-171r2.pdf
- Coverage: AVAILABLE

### 3.7.2 (Requirement)
3.7.2
Provide controls on the tools, techniques, mechanisms, and personnel used to conduct system maintenance.
- ChapterNumber: 3.7 MAINTENANCE
- Source File: NIST_SP_800-171r2.pdf
- Coverage: AVAILABLE

### 3.7.3 (Requirement)
3.7.3
Ensure equipment removed for off-site maintenance is sanitized of any CUI.
- ChapterNumber: 3.7 MAINTENANCE
- Source File: NIST_SP_800-171r2.pdf
- Coverage: AVAILABLE

### 3.7.4 (Requirement)
3.7.4
Check media containing diagnostic and test programs for malicious code before the media are used in organizational systems.
- ChapterNumber: 3.7 MAINTENANCE
- Source File: NIST_SP_800-171r2.pdf
- Coverage: AVAILABLE

### 3.7.5 (Requirement)
3.7.5
Require multifactor authentication to establish nonlocal maintenance sessions via external network connections and terminate such connections when nonlocal maintenance is complete.
- ChapterNumber: 3.7 MAINTENANCE
- Source File: NIST_SP_800-171r2.pdf
- Coverage: AVAILABLE

### 3.7.6 (Requirement)
3.7.6
Supervise the maintenance activities of maintenance personnel without required access authorization.
- ChapterNumber: 3.7 MAINTENANCE
- Source File: NIST_SP_800-171r2.pdf
- Coverage: AVAILABLE

## R8: MEDIA PROTECTION (Info)
- ChapterNumber: 3.8
- Level: 2

### 3.8.1 (Requirement)
3.8.1
Protect (i.e., physically control and securely store) system media containing CUI, both paper and digital.
- ChapterNumber: 3.8 MEDIA PROTECTION
- Source File: NIST_SP_800-171r2.pdf
- Coverage: AVAILABLE

### 3.8.2 (Requirement)
3.8.2
Limit access to CUI on system media to authorized users.
- ChapterNumber: 3.8 MEDIA PROTECTION
- Source File: NIST_SP_800-171r2.pdf
- Coverage: AVAILABLE

### 3.8.3 (Requirement)
3.8.3
Sanitize or destroy system media containing CUI before disposal or release for reuse.
- ChapterNumber: 3.8 MEDIA PROTECTION
- Source File: NIST_SP_800-171r2.pdf
- Coverage: AVAILABLE

### 3.8.4 (Requirement)
3.8.4
Mark media with necessary CUI markings and distribution limitations. 27
- ChapterNumber: 3.8 MEDIA PROTECTION
- Source File: NIST_SP_800-171r2.pdf
- Coverage: AVAILABLE

### 3.8.5 (Requirement)
3.8.5
Control access to media containing CUI and maintain accountability for media during transport outside of controlled areas.
- ChapterNumber: 3.8 MEDIA PROTECTION
- Source File: NIST_SP_800-171r2.pdf
- Coverage: AVAILABLE

### 3.8.6 (Requirement)
3.8.6
Implement cryptographic mechanisms to protect the confidentiality of CUI stored on digital media during transport unless otherwise protected by alternative physical safeguards.
- ChapterNumber: 3.8 MEDIA PROTECTION
- Source File: NIST_SP_800-171r2.pdf
- Coverage: AVAILABLE

### 3.8.7 (Requirement)
3.8.7
Control the use of removable media on system components.
- ChapterNumber: 3.8 MEDIA PROTECTION
- Source File: NIST_SP_800-171r2.pdf
- Coverage: AVAILABLE

### 3.8.8 (Requirement)
3.8.8
Prohibit the use of portable storage devices when such devices have no identifiable owner.
- ChapterNumber: 3.8 MEDIA PROTECTION
- Source File: NIST_SP_800-171r2.pdf
- Coverage: AVAILABLE

### 3.8.9 (Requirement)
3.8.9
Protect the confidentiality of backup CUI at storage locations.
- ChapterNumber: 3.8 MEDIA PROTECTION
- Source File: NIST_SP_800-171r2.pdf
- Coverage: AVAILABLE

## R9: PERSONNEL SECURITY (Info)
- ChapterNumber: 3.9
- Level: 2

### 3.9.1 (Requirement)
3.9.1
Screen individuals prior to authorizing access to organizational systems containing CUI.
- ChapterNumber: 3.9 PERSONNEL SECURITY
- Source File: NIST_SP_800-171r2.pdf
- Coverage: AVAILABLE

### 3.9.2 (Requirement)
3.9.2
Ensure that organizational systems containing CUI are protected during and after personnel actions such as terminations and transfers.
- ChapterNumber: 3.9 PERSONNEL SECURITY
- Source File: NIST_SP_800-171r2.pdf
- Coverage: AVAILABLE

## R10: PHYSICAL PROTECTION (Info)
- ChapterNumber: 3.10
- Level: 2

### 3.10.1 (Requirement)
3.10.1
Limit physical access to organizational systems, equipment, and the respective operating environments to authorized individuals.
- ChapterNumber: 3.10 PHYSICAL PROTECTION
- Source File: NIST_SP_800-171r2.pdf
- Coverage: AVAILABLE

### 3.10.2 (Requirement)
3.10.2
Protect and monitor the physical facility and support infrastructure for organizational systems.
- ChapterNumber: 3.10 PHYSICAL PROTECTION
- Source File: NIST_SP_800-171r2.pdf
- Coverage: AVAILABLE

### 3.10.3 (Requirement)
3.10.3
Escort visitors and monitor visitor activity.
- ChapterNumber: 3.10 PHYSICAL PROTECTION
- Source File: NIST_SP_800-171r2.pdf
- Coverage: AVAILABLE

### 3.10.4 (Requirement)
3.10.4
Maintain audit logs of physical access.
- ChapterNumber: 3.10 PHYSICAL PROTECTION
- Source File: NIST_SP_800-171r2.pdf
- Coverage: AVAILABLE

### 3.10.5 (Requirement)
3.10.5
Control and manage physical access devices.
- ChapterNumber: 3.10 PHYSICAL PROTECTION
- Source File: NIST_SP_800-171r2.pdf
- Coverage: AVAILABLE

### 3.10.6 (Requirement)
3.10.6
Enforce safeguarding measures for CUI at alternate work sites.
- ChapterNumber: 3.10 PHYSICAL PROTECTION
- Source File: NIST_SP_800-171r2.pdf
- Coverage: AVAILABLE

## R11: RISK ASSESSMENT (Info)
- ChapterNumber: 3.11
- Level: 2

### 3.11.1 (Requirement)
3.11.1
Periodically assess the risk to organizational operations (including mission, functions, image, or reputation), organizational assets, and individuals, resulting from the operation of organizational systems and the associated processing, storage, or transmission of CUI.
- ChapterNumber: 3.11 RISK ASSESSMENT
- Source File: NIST_SP_800-171r2.pdf
- Coverage: AVAILABLE

### 3.11.2 (Requirement)
3.11.2
Scan for vulnerabilities in organizational systems and applications periodically and when new vulnerabilities affecting those systems and applications are identified.
- ChapterNumber: 3.11 RISK ASSESSMENT
- Source File: NIST_SP_800-171r2.pdf
- Coverage: AVAILABLE

### 3.11.3 (Requirement)
3.11.3
Remediate vulnerabilities in accordance with risk assessments.
- ChapterNumber: 3.11 RISK ASSESSMENT
- Source File: NIST_SP_800-171r2.pdf
- Coverage: AVAILABLE

## R12: SECURITY ASSESSMENT (Info)
- ChapterNumber: 3.12
- Level: 2

### 3.12.1 (Requirement)
3.12.1
Periodically assess the security controls in organizational systems to determine if the controls are effective in their application.
- ChapterNumber: 3.12 SECURITY ASSESSMENT
- Source File: NIST_SP_800-171r2.pdf
- Coverage: AVAILABLE

### 3.12.2 (Requirement)
3.12.2
Develop and implement plans of action designed to correct deficiencies and reduce or eliminate vulnerabilities in organizational systems.
- ChapterNumber: 3.12 SECURITY ASSESSMENT
- Source File: NIST_SP_800-171r2.pdf
- Coverage: AVAILABLE

### 3.12.3 (Requirement)
3.12.3
Monitor security controls on an ongoing basis to ensure the continued effectiveness of the controls.
- ChapterNumber: 3.12 SECURITY ASSESSMENT
- Source File: NIST_SP_800-171r2.pdf
- Coverage: AVAILABLE

### 3.12.4 (Requirement)
3.12.4
Develop, document, and periodically update system security plans that describe system boundaries, system environments of operation, how security requirements are implemented, and the relationships with or connections to other systems. 28
- ChapterNumber: 3.12 SECURITY ASSESSMENT
- Source File: NIST_SP_800-171r2.pdf
- Coverage: AVAILABLE

## R13: SYSTEM AND COMMUNICATIONS PROTECTION (Info)
- ChapterNumber: 3.13
- Level: 2

### 3.13.1 (Requirement)
3.13.1
Monitor, control, and protect communications (i.e., information transmitted or received by organizational systems) at the external boundaries and key internal boundaries of organizational systems.
- ChapterNumber: 3.13 SYSTEM AND COMMUNICATIONS PROTECTION
- Source File: NIST_SP_800-171r2.pdf
- Coverage: AVAILABLE

### 3.13.2 (Requirement)
3.13.2
Employ architectural designs, software development techniques, and systems engineering principles that promote effective information security within organizational systems.
- ChapterNumber: 3.13 SYSTEM AND COMMUNICATIONS PROTECTION
- Source File: NIST_SP_800-171r2.pdf
- Coverage: AVAILABLE

### 3.13.3 (Requirement)
3.13.3
Separate user functionality from system management functionality.
- ChapterNumber: 3.13 SYSTEM AND COMMUNICATIONS PROTECTION
- Source File: NIST_SP_800-171r2.pdf
- Coverage: AVAILABLE

### 3.13.4 (Requirement)
3.13.4
Prevent unauthorized and unintended information transfer via shared system resources.
- ChapterNumber: 3.13 SYSTEM AND COMMUNICATIONS PROTECTION
- Source File: NIST_SP_800-171r2.pdf
- Coverage: AVAILABLE

### 3.13.5 (Requirement)
3.13.5
Implement subnetworks for publicly accessible system components that are physically or logically separated from internal networks.
- ChapterNumber: 3.13 SYSTEM AND COMMUNICATIONS PROTECTION
- Source File: NIST_SP_800-171r2.pdf
- Coverage: AVAILABLE

### 3.13.6 (Requirement)
3.13.6
Deny network communications traffic by default and allow network communications traffic by exception (i.e., deny all, permit by exception).
- ChapterNumber: 3.13 SYSTEM AND COMMUNICATIONS PROTECTION
- Source File: NIST_SP_800-171r2.pdf
- Coverage: AVAILABLE

### 3.13.7 (Requirement)
3.13.7
Prevent remote devices from simultaneously establishing non-remote connections with organizational systems and communicating via some other connection to resources in external networks (i.e., split tunneling).
- ChapterNumber: 3.13 SYSTEM AND COMMUNICATIONS PROTECTION
- Source File: NIST_SP_800-171r2.pdf
- Coverage: AVAILABLE

### 3.13.8 (Requirement)
3.13.8
Implement cryptographic mechanisms to prevent unauthorized disclosure of CUI during transmission unless otherwise protected by alternative physical safeguards.
- ChapterNumber: 3.13 SYSTEM AND COMMUNICATIONS PROTECTION
- Source File: NIST_SP_800-171r2.pdf
- Coverage: AVAILABLE

### 3.13.9 (Requirement)
3.13.9
Terminate network connections associated with communications sessions at the end of the sessions or after a defined period of inactivity.
- ChapterNumber: 3.13 SYSTEM AND COMMUNICATIONS PROTECTION
- Source File: NIST_SP_800-171r2.pdf
- Coverage: AVAILABLE

### 3.13.10 (Requirement)
3.13.10
Establish and manage cryptographic keys for cryptography employed in organizational systems.
- ChapterNumber: 3.13 SYSTEM AND COMMUNICATIONS PROTECTION
- Source File: NIST_SP_800-171r2.pdf
- Coverage: AVAILABLE

### 3.13.11 (Requirement)
3.13.11
Employ FIPS-validated cryptography when used to protect the confidentiality of CUI.
- ChapterNumber: 3.13 SYSTEM AND COMMUNICATIONS PROTECTION
- Source File: NIST_SP_800-171r2.pdf
- Coverage: AVAILABLE

### 3.13.12 (Requirement)
3.13.12
Prohibit remote activation of collaborative computing devices and provide indication of devices in use to users present at the device. 29
- ChapterNumber: 3.13 SYSTEM AND COMMUNICATIONS PROTECTION
- Source File: NIST_SP_800-171r2.pdf
- Coverage: AVAILABLE

### 3.13.13 (Requirement)
3.13.13
Control and monitor the use of mobile code.
- ChapterNumber: 3.13 SYSTEM AND COMMUNICATIONS PROTECTION
- Source File: NIST_SP_800-171r2.pdf
- Coverage: AVAILABLE

### 3.13.14 (Requirement)
3.13.14
Control and monitor the use of Voice over Internet Protocol (VoIP) technologies.
- ChapterNumber: 3.13 SYSTEM AND COMMUNICATIONS PROTECTION
- Source File: NIST_SP_800-171r2.pdf
- Coverage: AVAILABLE

### 3.13.15 (Requirement)
3.13.15
Protect the authenticity of communications sessions.
- ChapterNumber: 3.13 SYSTEM AND COMMUNICATIONS PROTECTION
- Source File: NIST_SP_800-171r2.pdf
- Coverage: AVAILABLE

### 3.13.16 (Requirement)
3.13.16
Protect the confidentiality of CUI at rest.
- ChapterNumber: 3.13 SYSTEM AND COMMUNICATIONS PROTECTION
- Source File: NIST_SP_800-171r2.pdf
- Coverage: AVAILABLE

## R14: SYSTEM AND INFORMATION INTEGRITY (Info)
- ChapterNumber: 3.14
- Level: 2

### 3.14.1 (Requirement)
3.14.1
Identify, report, and correct system flaws in a timely manner.
- ChapterNumber: 3.14 SYSTEM AND INFORMATION INTEGRITY
- Source File: NIST_SP_800-171r2.pdf
- Coverage: AVAILABLE

### 3.14.2 (Requirement)
3.14.2
Provide protection from malicious code at designated locations within organizational systems.
- ChapterNumber: 3.14 SYSTEM AND INFORMATION INTEGRITY
- Source File: NIST_SP_800-171r2.pdf
- Coverage: AVAILABLE

### 3.14.3 (Requirement)
3.14.3
Monitor system security alerts and advisories and take action in response.
- ChapterNumber: 3.14 SYSTEM AND INFORMATION INTEGRITY
- Source File: NIST_SP_800-171r2.pdf
- Coverage: AVAILABLE

### 3.14.4 (Requirement)
3.14.4
Update malicious code protection mechanisms when new releases are available.
- ChapterNumber: 3.14 SYSTEM AND INFORMATION INTEGRITY
- Source File: NIST_SP_800-171r2.pdf
- Coverage: AVAILABLE

### 3.14.5 (Requirement)
3.14.5
Perform periodic scans of organizational systems and real-time scans of files from external sources as files are downloaded, opened, or executed.
- ChapterNumber: 3.14 SYSTEM AND INFORMATION INTEGRITY
- Source File: NIST_SP_800-171r2.pdf
- Coverage: AVAILABLE

### 3.14.6 (Requirement)
3.14.6
Monitor organizational systems, including inbound and outbound communications traffic, to detect attacks and indicators of potential attacks.
- ChapterNumber: 3.14 SYSTEM AND INFORMATION INTEGRITY
- Source File: NIST_SP_800-171r2.pdf
- Coverage: AVAILABLE

### 3.14.7 (Requirement)
3.14.7
Identify unauthorized use of organizational systems.
- ChapterNumber: 3.14 SYSTEM AND INFORMATION INTEGRITY
- Source File: NIST_SP_800-171r2.pdf
- Coverage: AVAILABLE

## R15: MAPPING TABLES (Info)
- Level: 2

### A.8.2.3* (Requirement)
A.8.2.3*
Handling of Assets
- ChapterNumber: MAPPING TABLES
- Source File: NIST_SP_800-171r2.pdf
- Coverage: AVAILABLE

### A.12.6.1 (Requirement)
A.12.6.1
Management of technical vulnerabilities
- ChapterNumber: MAPPING TABLES
- Source File: NIST_SP_800-171r2.pdf
- Coverage: AVAILABLE

### A.14.2.2 (Requirement)
A.14.2.2
System change control procedures
- ChapterNumber: MAPPING TABLES
- Source File: NIST_SP_800-171r2.pdf
- Coverage: AVAILABLE

### A.14.2.3 (Requirement)
A.14.2.3
Technical review of applications after operating platform changes
- ChapterNumber: MAPPING TABLES
- Source File: NIST_SP_800-171r2.pdf
- Coverage: AVAILABLE

### A.16.1.3 (Requirement)
A.16.1.3
Reporting information security weaknesses
- ChapterNumber: MAPPING TABLES
- Source File: NIST_SP_800-171r2.pdf
- Coverage: AVAILABLE

### A.12.2.1 (Requirement)
A.12.2.1
Controls against malware
- ChapterNumber: MAPPING TABLES
- Source File: NIST_SP_800-171r2.pdf
- Coverage: AVAILABLE

### A.6.1.4* (Requirement)
A.6.1.4*
Contact with special interest groups
- ChapterNumber: MAPPING TABLES
- Source File: NIST_SP_800-171r2.pdf
- Coverage: AVAILABLE

## R16: TAILORING CRITERIA (Info)
- Level: 2

### AT-1 (Requirement)
AT-1
Security Awareness and Training Policy and Procedures
- ChapterNumber: TAILORING CRITERIA
- Source File: NIST_SP_800-171r2.pdf
- Coverage: AVAILABLE

### AT-2 (Requirement)
AT-2
Security Awareness Training
- ChapterNumber: TAILORING CRITERIA
- Source File: NIST_SP_800-171r2.pdf
- Coverage: AVAILABLE

### AT-2(2) (Requirement)
AT-2(2)
SECURITY AWARENESS | INSIDER THREAT
- ChapterNumber: TAILORING CRITERIA
- Source File: NIST_SP_800-171r2.pdf
- Coverage: AVAILABLE

### AT-3 (Requirement)
AT-3
Role-Based Security Training
- ChapterNumber: TAILORING CRITERIA
- Source File: NIST_SP_800-171r2.pdf
- Coverage: AVAILABLE

### AT-4 (Requirement)
AT-4
Security Training Records
- ChapterNumber: TAILORING CRITERIA
- Source File: NIST_SP_800-171r2.pdf
- Coverage: AVAILABLE

### AU-1 (Requirement)
AU-1
Audit and Accountability Policy and Procedures
- ChapterNumber: TAILORING CRITERIA
- Source File: NIST_SP_800-171r2.pdf
- Coverage: AVAILABLE

### AU-2 (Requirement)
AU-2
Audit Events
- ChapterNumber: TAILORING CRITERIA
- Source File: NIST_SP_800-171r2.pdf
- Coverage: AVAILABLE

### AU-2(3) (Requirement)
AU-2(3)
AUDIT EVENTS | REVIEWS AND UPDATES
- ChapterNumber: TAILORING CRITERIA
- Source File: NIST_SP_800-171r2.pdf
- Coverage: AVAILABLE

### AU-3 (Requirement)
AU-3
Content of Audit Records
- ChapterNumber: TAILORING CRITERIA
- Source File: NIST_SP_800-171r2.pdf
- Coverage: AVAILABLE

### AU-3(1) (Requirement)
AU-3(1)
CONTENT OF AUDIT RECORDS | ADDITIONAL AUDIT INFORMATION
- ChapterNumber: TAILORING CRITERIA
- Source File: NIST_SP_800-171r2.pdf
- Coverage: AVAILABLE

### AU-4 (Requirement)
AU-4
Audit Storage Capacity
- ChapterNumber: TAILORING CRITERIA
- Source File: NIST_SP_800-171r2.pdf
- Coverage: AVAILABLE

### AU-5 (Requirement)
AU-5
Response to Audit Logging Process Failures
- ChapterNumber: TAILORING CRITERIA
- Source File: NIST_SP_800-171r2.pdf
- Coverage: AVAILABLE

### AU-6 (Requirement)
AU-6
Audit Review, Analysis, and Reporting
- ChapterNumber: TAILORING CRITERIA
- Source File: NIST_SP_800-171r2.pdf
- Coverage: AVAILABLE

### AU-6(1) (Requirement)
AU-6(1)
AUDIT REVIEW, ANALYSIS, AND REPORTING | PROCESS INTEGRATION
- ChapterNumber: TAILORING CRITERIA
- Source File: NIST_SP_800-171r2.pdf
- Coverage: AVAILABLE

### AU-6(3) (Requirement)
AU-6(3)
AUDIT REVIEW, ANALYSIS, AND REPORTING | CORRELATE AUDIT REPOSITORIES
- ChapterNumber: TAILORING CRITERIA
- Source File: NIST_SP_800-171r2.pdf
- Coverage: AVAILABLE

### AU-7 (Requirement)
AU-7
Audit Reduction and Report Generation
- ChapterNumber: TAILORING CRITERIA
- Source File: NIST_SP_800-171r2.pdf
- Coverage: AVAILABLE

### AU-7(1) (Requirement)
AU-7(1)
AUDIT REDUCTION AND REPORT GENERATION | AUTOMATIC PROCESSING
- ChapterNumber: TAILORING CRITERIA
- Source File: NIST_SP_800-171r2.pdf
- Coverage: AVAILABLE

### AU-8 (Requirement)
AU-8
Time Stamps
- ChapterNumber: TAILORING CRITERIA
- Source File: NIST_SP_800-171r2.pdf
- Coverage: AVAILABLE

### AU-8(1) (Requirement)
AU-8(1)
TIME STAMPS | SYNCHRONIZATION WITH AUTHORITATIVE TIME SOURCE
- ChapterNumber: TAILORING CRITERIA
- Source File: NIST_SP_800-171r2.pdf
- Coverage: AVAILABLE

### AU-9 (Requirement)
AU-9
Protection of Audit Information
- ChapterNumber: TAILORING CRITERIA
- Source File: NIST_SP_800-171r2.pdf
- Coverage: AVAILABLE

### AU-9(4) (Requirement)
AU-9(4)
PROTECTION OF AUDIT INFORMATION | ACCESS BY SUBSET OF PRIVILEGED USERS
- ChapterNumber: TAILORING CRITERIA
- Source File: NIST_SP_800-171r2.pdf
- Coverage: AVAILABLE

### AU-11 (Requirement)
AU-11
Audit Record Retention
- ChapterNumber: TAILORING CRITERIA
- Source File: NIST_SP_800-171r2.pdf
- Coverage: AVAILABLE

### AU-12 (Requirement)
AU-12
Audit Generation
- ChapterNumber: TAILORING CRITERIA
- Source File: NIST_SP_800-171r2.pdf
- Coverage: AVAILABLE

### CA-1 (Requirement)
CA-1
Security Assessment and Authorization Policies and Procedures
- ChapterNumber: TAILORING CRITERIA
- Source File: NIST_SP_800-171r2.pdf
- Coverage: AVAILABLE

### CA-2 (Requirement)
CA-2
Security Assessments
- ChapterNumber: TAILORING CRITERIA
- Source File: NIST_SP_800-171r2.pdf
- Coverage: AVAILABLE

### CA-2(1) (Requirement)
CA-2(1)
SECURITY ASSESSMENTS | INDEPENDENT ASSESSORS
- ChapterNumber: TAILORING CRITERIA
- Source File: NIST_SP_800-171r2.pdf
- Coverage: AVAILABLE

### CA-3 (Requirement)
CA-3
System Interconnections
- ChapterNumber: TAILORING CRITERIA
- Source File: NIST_SP_800-171r2.pdf
- Coverage: AVAILABLE

### CA-3(5) (Requirement)
CA-3(5)
SYSTEM INTERCONNECTIONS | RESTRICTIONS ON EXTERNAL SYSTEM CONNECTIONS
- ChapterNumber: TAILORING CRITERIA
- Source File: NIST_SP_800-171r2.pdf
- Coverage: AVAILABLE

### CA-5 (Requirement)
CA-5
Plan of Action and Milestones
- ChapterNumber: TAILORING CRITERIA
- Source File: NIST_SP_800-171r2.pdf
- Coverage: AVAILABLE

### CA-6 (Requirement)
CA-6
Security Authorization
- ChapterNumber: TAILORING CRITERIA
- Source File: NIST_SP_800-171r2.pdf
- Coverage: AVAILABLE

### CA-7 (Requirement)
CA-7
Continuous Monitoring
- ChapterNumber: TAILORING CRITERIA
- Source File: NIST_SP_800-171r2.pdf
- Coverage: AVAILABLE

### CA-7(1) (Requirement)
CA-7(1)
CONTINUOUS MONITORING | INDEPENDENT ASSESSMENT
- ChapterNumber: TAILORING CRITERIA
- Source File: NIST_SP_800-171r2.pdf
- Coverage: AVAILABLE

### CA-9 (Requirement)
CA-9
Internal System Connections
- ChapterNumber: TAILORING CRITERIA
- Source File: NIST_SP_800-171r2.pdf
- Coverage: AVAILABLE

### CM-1 (Requirement)
CM-1
Configuration Management Policy and Procedures
- ChapterNumber: TAILORING CRITERIA
- Source File: NIST_SP_800-171r2.pdf
- Coverage: AVAILABLE

### CM-2 (Requirement)
CM-2
Baseline Configuration
- ChapterNumber: TAILORING CRITERIA
- Source File: NIST_SP_800-171r2.pdf
- Coverage: AVAILABLE

### CM-2(1) (Requirement)
CM-2(1)
BASELINE CONFIGURATION | REVIEWS AND UPDATES
- ChapterNumber: TAILORING CRITERIA
- Source File: NIST_SP_800-171r2.pdf
- Coverage: AVAILABLE

### CM-2(3) (Requirement)
CM-2(3)
BASELINE CONFIGURATION | RETENTION OF PREVIOUS CONFIGURATIONS
- ChapterNumber: TAILORING CRITERIA
- Source File: NIST_SP_800-171r2.pdf
- Coverage: AVAILABLE

### CM-2(7) (Requirement)
CM-2(7)
BASELINE CONFIGURATION | CONFIGURE SYSTEMS, COMPONENTS, OR DEVICES FOR HIGH-RISK AREAS
- ChapterNumber: TAILORING CRITERIA
- Source File: NIST_SP_800-171r2.pdf
- Coverage: AVAILABLE

### CM-3 (Requirement)
CM-3
Configuration Change Control
- ChapterNumber: TAILORING CRITERIA
- Source File: NIST_SP_800-171r2.pdf
- Coverage: AVAILABLE

### CM-3(2) (Requirement)
CM-3(2)
CONFIGURATION CHANGE CONTROL | TEST / VALIDATE / DOCUMENT CHANGES
- ChapterNumber: TAILORING CRITERIA
- Source File: NIST_SP_800-171r2.pdf
- Coverage: AVAILABLE

### CM-4 (Requirement)
CM-4
Security Impact Analysis
- ChapterNumber: TAILORING CRITERIA
- Source File: NIST_SP_800-171r2.pdf
- Coverage: AVAILABLE

### CM-5 (Requirement)
CM-5
Access Restrictions for Change
- ChapterNumber: TAILORING CRITERIA
- Source File: NIST_SP_800-171r2.pdf
- Coverage: AVAILABLE

### CM-6 (Requirement)
CM-6
Configuration Settings
- ChapterNumber: TAILORING CRITERIA
- Source File: NIST_SP_800-171r2.pdf
- Coverage: AVAILABLE

### CM-7 (Requirement)
CM-7
Least Functionality
- ChapterNumber: TAILORING CRITERIA
- Source File: NIST_SP_800-171r2.pdf
- Coverage: AVAILABLE

### CM-7(1) (Requirement)
CM-7(1)
LEAST FUNCTIONALITY | PERIODIC REVIEW
- ChapterNumber: TAILORING CRITERIA
- Source File: NIST_SP_800-171r2.pdf
- Coverage: AVAILABLE

### CM-7(2) (Requirement)
CM-7(2)
LEAST FUNCTIONALITY | PREVENT PROGRAM EXECUTION
- ChapterNumber: TAILORING CRITERIA
- Source File: NIST_SP_800-171r2.pdf
- Coverage: AVAILABLE

### CM-7(4)(5) (Requirement)
CM-7(4)(5)
LEAST FUNCTIONALITY | UNAUTHORIZED OR AUTHORIZED SOFTWARE / BLACKLISTING OR WHITELISTING
- ChapterNumber: TAILORING CRITERIA
- Source File: NIST_SP_800-171r2.pdf
- Coverage: AVAILABLE

### CM-8 (Requirement)
CM-8
System Component Inventory
- ChapterNumber: TAILORING CRITERIA
- Source File: NIST_SP_800-171r2.pdf
- Coverage: AVAILABLE

### CM-8(1) (Requirement)
CM-8(1)
SYSTEM COMPONENT INVENTORY | UPDATES DURING INSTALLATIONS / REMOVALS
- ChapterNumber: TAILORING CRITERIA
- Source File: NIST_SP_800-171r2.pdf
- Coverage: AVAILABLE

### CM-8(3) (Requirement)
CM-8(3)
SYSTEM COMPONENT INVENTORY | AUTOMATED UNAUTHORIZED COMPONENT DETECTION
- ChapterNumber: TAILORING CRITERIA
- Source File: NIST_SP_800-171r2.pdf
- Coverage: AVAILABLE

### CM-8(5) (Requirement)
CM-8(5)
SYSTEM COMPONENT INVENTORY | NO DUPLICATE ACCOUNTING OF COMPONENTS
- ChapterNumber: TAILORING CRITERIA
- Source File: NIST_SP_800-171r2.pdf
- Coverage: AVAILABLE

### CM-9 (Requirement)
CM-9
Configuration Management Plan
- ChapterNumber: TAILORING CRITERIA
- Source File: NIST_SP_800-171r2.pdf
- Coverage: AVAILABLE

### CM-10 (Requirement)
CM-10
Software Usage Restrictions
- ChapterNumber: TAILORING CRITERIA
- Source File: NIST_SP_800-171r2.pdf
- Coverage: AVAILABLE

### CM-11 (Requirement)
CM-11
User-Installed Software
- ChapterNumber: TAILORING CRITERIA
- Source File: NIST_SP_800-171r2.pdf
- Coverage: AVAILABLE

### CP-1 (Requirement)
CP-1
Contingency Planning Policy and Procedures
- ChapterNumber: TAILORING CRITERIA
- Source File: NIST_SP_800-171r2.pdf
- Coverage: AVAILABLE

### CP-2 (Requirement)
CP-2
Contingency Plan
- ChapterNumber: TAILORING CRITERIA
- Source File: NIST_SP_800-171r2.pdf
- Coverage: AVAILABLE

### CP-2(1) (Requirement)
CP-2(1)
CONTINGENCY PLAN | COORDINATE WITH RELATED PLANS
- ChapterNumber: TAILORING CRITERIA
- Source File: NIST_SP_800-171r2.pdf
- Coverage: AVAILABLE

### CP-2(3) (Requirement)
CP-2(3)
CONTINGENCY PLAN | RESUME ESSENTIAL MISSIONS / BUSINESS FUNCTIONS
- ChapterNumber: TAILORING CRITERIA
- Source File: NIST_SP_800-171r2.pdf
- Coverage: AVAILABLE

### CP-2(8) (Requirement)
CP-2(8)
CONTINGENCY PLAN | IDENTIFY CRITICAL ASSETS
- ChapterNumber: TAILORING CRITERIA
- Source File: NIST_SP_800-171r2.pdf
- Coverage: AVAILABLE

### CP-3 (Requirement)
CP-3
Contingency Training
- ChapterNumber: TAILORING CRITERIA
- Source File: NIST_SP_800-171r2.pdf
- Coverage: AVAILABLE

### CP-4 (Requirement)
CP-4
Contingency Plan Testing
- ChapterNumber: TAILORING CRITERIA
- Source File: NIST_SP_800-171r2.pdf
- Coverage: AVAILABLE

### CP-4(1) (Requirement)
CP-4(1)
CONTINGENCY PLAN TESTING | COORDINATE WITH RELATED PLANS
- ChapterNumber: TAILORING CRITERIA
- Source File: NIST_SP_800-171r2.pdf
- Coverage: AVAILABLE

### CP-6 (Requirement)
CP-6
Alternate Storage Site
- ChapterNumber: TAILORING CRITERIA
- Source File: NIST_SP_800-171r2.pdf
- Coverage: AVAILABLE

### CP-6(1) (Requirement)
CP-6(1)
ALTERNATE STORAGE SITE | SEPARATION FROM PRIMARY SITE
- ChapterNumber: TAILORING CRITERIA
- Source File: NIST_SP_800-171r2.pdf
- Coverage: AVAILABLE

### CP-6(3) (Requirement)
CP-6(3)
ALTERNATE STORAGE SITE | ACCESSIBILITY
- ChapterNumber: TAILORING CRITERIA
- Source File: NIST_SP_800-171r2.pdf
- Coverage: AVAILABLE

### CP-7 (Requirement)
CP-7
Alternate Processing Site
- ChapterNumber: TAILORING CRITERIA
- Source File: NIST_SP_800-171r2.pdf
- Coverage: AVAILABLE

### CP-7(1) (Requirement)
CP-7(1)
ALTERNATE PROCESSING SITE | SEPARATION FROM PRIMARY SITE
- ChapterNumber: TAILORING CRITERIA
- Source File: NIST_SP_800-171r2.pdf
- Coverage: AVAILABLE

### CP-7(2) (Requirement)
CP-7(2)
ALTERNATE PROCESSING SITE | ACCESSIBILITY
- ChapterNumber: TAILORING CRITERIA
- Source File: NIST_SP_800-171r2.pdf
- Coverage: AVAILABLE

### CP-7(3) (Requirement)
CP-7(3)
ALTERNATE PROCESSING SITE | PRIORITY OF SERVICE
- ChapterNumber: TAILORING CRITERIA
- Source File: NIST_SP_800-171r2.pdf
- Coverage: AVAILABLE

### CP-8 (Requirement)
CP-8
Telecommunications Services
- ChapterNumber: TAILORING CRITERIA
- Source File: NIST_SP_800-171r2.pdf
- Coverage: AVAILABLE

### CP-8(1) (Requirement)
CP-8(1)
TELECOMMUNICATIONS SERVICES | PRIORITY OF SERVICE PROVISIONS
- ChapterNumber: TAILORING CRITERIA
- Source File: NIST_SP_800-171r2.pdf
- Coverage: AVAILABLE

### CP-8(2) (Requirement)
CP-8(2)
TELECOMMUNICATIONS SERVICES | SINGLE POINTS OF FAILURE
- ChapterNumber: TAILORING CRITERIA
- Source File: NIST_SP_800-171r2.pdf
- Coverage: AVAILABLE

### CP-9 (Requirement)
CP-9
System Backup
- ChapterNumber: TAILORING CRITERIA
- Source File: NIST_SP_800-171r2.pdf
- Coverage: AVAILABLE

### CP-9(1) (Requirement)
CP-9(1)
SYSTEM BACKUP | TESTING FOR RELIABILITY / INTEGRITY
- ChapterNumber: TAILORING CRITERIA
- Source File: NIST_SP_800-171r2.pdf
- Coverage: AVAILABLE

### CP-10 (Requirement)
CP-10
System Recovery and Reconstitution
- ChapterNumber: TAILORING CRITERIA
- Source File: NIST_SP_800-171r2.pdf
- Coverage: AVAILABLE

### CP-10(2) (Requirement)
CP-10(2)
SYSTEM RECOVERY AND RECONSTITUTION | TRANSACTION RECOVERY
- ChapterNumber: TAILORING CRITERIA
- Source File: NIST_SP_800-171r2.pdf
- Coverage: AVAILABLE

### IA-1 (Requirement)
IA-1
Identification and Authentication Policy and Procedures
- ChapterNumber: TAILORING CRITERIA
- Source File: NIST_SP_800-171r2.pdf
- Coverage: AVAILABLE

### IA-2 (Requirement)
IA-2
Identification and Authentication (Organizational Users)
- ChapterNumber: TAILORING CRITERIA
- Source File: NIST_SP_800-171r2.pdf
- Coverage: AVAILABLE

### IA-2(1) (Requirement)
IA-2(1)
IDENTIFICATION AND AUTHENTICATION (ORGANIZATIONAL USERS) | NETWORK ACCESS TO PRIVILEGED ACCOUNTS
- ChapterNumber: TAILORING CRITERIA
- Source File: NIST_SP_800-171r2.pdf
- Coverage: AVAILABLE

### IA-2(2) (Requirement)
IA-2(2)
IDENTIFICATION AND AUTHENTICATION (ORGANIZATIONAL USERS) | NETWORK ACCESS TO NON-PRIVILEGED ACCOUNTS
- ChapterNumber: TAILORING CRITERIA
- Source File: NIST_SP_800-171r2.pdf
- Coverage: AVAILABLE

### IA-2(3) (Requirement)
IA-2(3)
IDENTIFICATION AND AUTHENTICATION (ORGANIZATIONAL USERS) | LOCAL ACCESS TO PRIVILEGED ACCOUNTS
- ChapterNumber: TAILORING CRITERIA
- Source File: NIST_SP_800-171r2.pdf
- Coverage: AVAILABLE

### IA-2(8) (Requirement)
IA-2(8)
IDENTIFICATION AND AUTHENTICATION (ORGANIZATIONAL USERS) | NETWORK ACCESS TO PRIVILEGED ACCOUNTS - REPLAY RESISTANT
- ChapterNumber: TAILORING CRITERIA
- Source File: NIST_SP_800-171r2.pdf
- Coverage: AVAILABLE

### IA-2(9) (Requirement)
IA-2(9)
IDENTIFICATION AND AUTHENTICATION (ORGANIZATIONAL USERS) | NETWORK ACCESS TO NON-PRIVILEGED ACCOUNTS - REPLAY RESISTANT
- ChapterNumber: TAILORING CRITERIA
- Source File: NIST_SP_800-171r2.pdf
- Coverage: AVAILABLE

### IA-2(11) (Requirement)
IA-2(11)
IDENTIFICATION AND AUTHENTICATION (ORGANIZATIONAL USERS) | REMOTE ACCESS - SEPARATE DEVICE
- ChapterNumber: TAILORING CRITERIA
- Source File: NIST_SP_800-171r2.pdf
- Coverage: AVAILABLE

### IA-2(12) (Requirement)
IA-2(12)
IDENTIFICATION AND AUTHENTICATION (ORGANIZATIONAL USERS) | ACCEPTANCE OF PIV CREDENTIALS
- ChapterNumber: TAILORING CRITERIA
- Source File: NIST_SP_800-171r2.pdf
- Coverage: AVAILABLE

### IA-3 (Requirement)
IA-3
Device Identification and Authentication
- ChapterNumber: TAILORING CRITERIA
- Source File: NIST_SP_800-171r2.pdf
- Coverage: AVAILABLE

### IA-4 (Requirement)
IA-4
Identifier Management
- ChapterNumber: TAILORING CRITERIA
- Source File: NIST_SP_800-171r2.pdf
- Coverage: AVAILABLE

### IA-5 (Requirement)
IA-5
Authenticator Management
- ChapterNumber: TAILORING CRITERIA
- Source File: NIST_SP_800-171r2.pdf
- Coverage: AVAILABLE

### IA-5(1) (Requirement)
IA-5(1)
AUTHENTICATOR MANAGEMENT | PASSWORD-BASED AUTHENTICATION
- ChapterNumber: TAILORING CRITERIA
- Source File: NIST_SP_800-171r2.pdf
- Coverage: AVAILABLE

### IA-5(2) (Requirement)
IA-5(2)
AUTHENTICATOR MANAGEMENT | PKI-BASED AUTHENTICATION
- ChapterNumber: TAILORING CRITERIA
- Source File: NIST_SP_800-171r2.pdf
- Coverage: AVAILABLE

### IA-5(3) (Requirement)
IA-5(3)
AUTHENTICATOR MANAGEMENT | IN-PERSON OR TRUSTED THIRD-PARTY REGISTRATION
- ChapterNumber: TAILORING CRITERIA
- Source File: NIST_SP_800-171r2.pdf
- Coverage: AVAILABLE

### IA-5(11) (Requirement)
IA-5(11)
AUTHENTICATOR MANAGEMENT | HARDWARE TOKEN-BASED AUTHENTICATION
- ChapterNumber: TAILORING CRITERIA
- Source File: NIST_SP_800-171r2.pdf
- Coverage: AVAILABLE

### IA-6 (Requirement)
IA-6
Authenticator Feedback
- ChapterNumber: TAILORING CRITERIA
- Source File: NIST_SP_800-171r2.pdf
- Coverage: AVAILABLE

### IA-7 (Requirement)
IA-7
Cryptographic Module Authentication
- ChapterNumber: TAILORING CRITERIA
- Source File: NIST_SP_800-171r2.pdf
- Coverage: AVAILABLE

### IA-8 (Requirement)
IA-8
Identification and Authentication (Non-Organizational Users)
- ChapterNumber: TAILORING CRITERIA
- Source File: NIST_SP_800-171r2.pdf
- Coverage: AVAILABLE

### IA-8(1) (Requirement)
IA-8(1)
IDENTIFICATION AND AUTHENTICATION (NON-ORGANIZATIONAL USERS) | ACCEPTANCE OF PIV CREDENTIALS FROM OTHER AGENCIES
- ChapterNumber: TAILORING CRITERIA
- Source File: NIST_SP_800-171r2.pdf
- Coverage: AVAILABLE

### IA-8(2) (Requirement)
IA-8(2)
IDENTIFICATION AND AUTHENTICATION (NON-ORGANIZATIONAL USERS) | ACCEPTANCE OF THIRD-PARTY CREDENTIALS
- ChapterNumber: TAILORING CRITERIA
- Source File: NIST_SP_800-171r2.pdf
- Coverage: AVAILABLE

### IA-8(3) (Requirement)
IA-8(3)
IDENTIFICATION AND AUTHENTICATION (NON-ORGANIZATIONAL USERS) | USE OF FICAM-APPROVED PRODUCTS
- ChapterNumber: TAILORING CRITERIA
- Source File: NIST_SP_800-171r2.pdf
- Coverage: AVAILABLE

### IA-8(4) (Requirement)
IA-8(4)
IDENTIFICATION AND AUTHENTICATION (NON-ORGANIZATIONAL USERS) | USE OF FICAM-ISSUED PROFILES
- ChapterNumber: TAILORING CRITERIA
- Source File: NIST_SP_800-171r2.pdf
- Coverage: AVAILABLE

### IR-1 (Requirement)
IR-1
Incident Response Policy and Procedures
- ChapterNumber: TAILORING CRITERIA
- Source File: NIST_SP_800-171r2.pdf
- Coverage: AVAILABLE

### IR-2 (Requirement)
IR-2
Incident Response Training
- ChapterNumber: TAILORING CRITERIA
- Source File: NIST_SP_800-171r2.pdf
- Coverage: AVAILABLE

### IR-3 (Requirement)
IR-3
Incident Response Testing
- ChapterNumber: TAILORING CRITERIA
- Source File: NIST_SP_800-171r2.pdf
- Coverage: AVAILABLE

### IR-3(2) (Requirement)
IR-3(2)
INCIDENT RESPONSE TESTING | COORDINATION WITH RELATED PLANS
- ChapterNumber: TAILORING CRITERIA
- Source File: NIST_SP_800-171r2.pdf
- Coverage: AVAILABLE

### IR-4 (Requirement)
IR-4
Incident Handling
- ChapterNumber: TAILORING CRITERIA
- Source File: NIST_SP_800-171r2.pdf
- Coverage: AVAILABLE

### IR-4(1) (Requirement)
IR-4(1)
INCIDENT HANDLING | AUTOMATED INCIDENT HANDLING PROCESSES
- ChapterNumber: TAILORING CRITERIA
- Source File: NIST_SP_800-171r2.pdf
- Coverage: AVAILABLE

### IR-5 (Requirement)
IR-5
Incident Monitoring
- ChapterNumber: TAILORING CRITERIA
- Source File: NIST_SP_800-171r2.pdf
- Coverage: AVAILABLE

### IR-6 (Requirement)
IR-6
Incident Reporting
- ChapterNumber: TAILORING CRITERIA
- Source File: NIST_SP_800-171r2.pdf
- Coverage: AVAILABLE

### IR-6(1) (Requirement)
IR-6(1)
INCIDENT REPORTING | AUTOMATED REPORTING
- ChapterNumber: TAILORING CRITERIA
- Source File: NIST_SP_800-171r2.pdf
- Coverage: AVAILABLE

### IR-7 (Requirement)
IR-7
Incident Response Assistance
- ChapterNumber: TAILORING CRITERIA
- Source File: NIST_SP_800-171r2.pdf
- Coverage: AVAILABLE

### IR-7(1) (Requirement)
IR-7(1)
INCIDENT RESPONSE ASSISTANCE | AUTOMATION SUPPORT FOR AVAILABILITY OF INFORMATION / SUPPORT
- ChapterNumber: TAILORING CRITERIA
- Source File: NIST_SP_800-171r2.pdf
- Coverage: AVAILABLE

### IR-8 (Requirement)
IR-8
Incident Response Plan
- ChapterNumber: TAILORING CRITERIA
- Source File: NIST_SP_800-171r2.pdf
- Coverage: AVAILABLE

### MA-1 (Requirement)
MA-1
System Maintenance Policy and Procedures
- ChapterNumber: TAILORING CRITERIA
- Source File: NIST_SP_800-171r2.pdf
- Coverage: AVAILABLE

### MA-2 (Requirement)
MA-2
Controlled Maintenance
- ChapterNumber: TAILORING CRITERIA
- Source File: NIST_SP_800-171r2.pdf
- Coverage: AVAILABLE

### MA-3 (Requirement)
MA-3
Maintenance Tools
- ChapterNumber: TAILORING CRITERIA
- Source File: NIST_SP_800-171r2.pdf
- Coverage: AVAILABLE

### MA-3(1) (Requirement)
MA-3(1)
MAINTENANCE TOOLS | INSPECT TOOLS
- ChapterNumber: TAILORING CRITERIA
- Source File: NIST_SP_800-171r2.pdf
- Coverage: AVAILABLE

### MA-3(2) (Requirement)
MA-3(2)
MAINTENANCE TOOLS | INSPECT MEDIA
- ChapterNumber: TAILORING CRITERIA
- Source File: NIST_SP_800-171r2.pdf
- Coverage: AVAILABLE

### MA-4 (Requirement)
MA-4
Nonlocal Maintenance
- ChapterNumber: TAILORING CRITERIA
- Source File: NIST_SP_800-171r2.pdf
- Coverage: AVAILABLE

### MA-4(2) (Requirement)
MA-4(2)
NONLOCAL MAINTENANCE | DOCUMENT NONLOCAL MAINTENANCE
- ChapterNumber: TAILORING CRITERIA
- Source File: NIST_SP_800-171r2.pdf
- Coverage: AVAILABLE

### MA-5 (Requirement)
MA-5
Maintenance Personnel
- ChapterNumber: TAILORING CRITERIA
- Source File: NIST_SP_800-171r2.pdf
- Coverage: AVAILABLE

### MA-6 (Requirement)
MA-6
Timely Maintenance
- ChapterNumber: TAILORING CRITERIA
- Source File: NIST_SP_800-171r2.pdf
- Coverage: AVAILABLE

### MP-1 (Requirement)
MP-1
Media Protection Policy and Procedures
- ChapterNumber: TAILORING CRITERIA
- Source File: NIST_SP_800-171r2.pdf
- Coverage: AVAILABLE

### MP-2 (Requirement)
MP-2
Media Access
- ChapterNumber: TAILORING CRITERIA
- Source File: NIST_SP_800-171r2.pdf
- Coverage: AVAILABLE

### MP-3 (Requirement)
MP-3
Media Marking
- ChapterNumber: TAILORING CRITERIA
- Source File: NIST_SP_800-171r2.pdf
- Coverage: AVAILABLE

### MP-4 (Requirement)
MP-4
Media Storage
- ChapterNumber: TAILORING CRITERIA
- Source File: NIST_SP_800-171r2.pdf
- Coverage: AVAILABLE

### MP-5 (Requirement)
MP-5
Media Transport
- ChapterNumber: TAILORING CRITERIA
- Source File: NIST_SP_800-171r2.pdf
- Coverage: AVAILABLE

### MP-5(4) (Requirement)
MP-5(4)
MEDIA TRANSPORT | CRYPTOGRAPHIC PROTECTION
- ChapterNumber: TAILORING CRITERIA
- Source File: NIST_SP_800-171r2.pdf
- Coverage: AVAILABLE

### MP-6 (Requirement)
MP-6
Media Sanitization
- ChapterNumber: TAILORING CRITERIA
- Source File: NIST_SP_800-171r2.pdf
- Coverage: AVAILABLE

### MP-7 (Requirement)
MP-7
Media Use
- ChapterNumber: TAILORING CRITERIA
- Source File: NIST_SP_800-171r2.pdf
- Coverage: AVAILABLE

### MP-7(1) (Requirement)
MP-7(1)
MEDIA USE | PROHIBIT USE WITHOUT OWNER
- ChapterNumber: TAILORING CRITERIA
- Source File: NIST_SP_800-171r2.pdf
- Coverage: AVAILABLE

### PE-1 (Requirement)
PE-1
Physical and Environmental Protection Policy and Procedures
- ChapterNumber: TAILORING CRITERIA
- Source File: NIST_SP_800-171r2.pdf
- Coverage: AVAILABLE

### PE-2 (Requirement)
PE-2
Physical Access Authorizations
- ChapterNumber: TAILORING CRITERIA
- Source File: NIST_SP_800-171r2.pdf
- Coverage: AVAILABLE

### PE-3 (Requirement)
PE-3
Physical Access Control
- ChapterNumber: TAILORING CRITERIA
- Source File: NIST_SP_800-171r2.pdf
- Coverage: AVAILABLE

### PE-4 (Requirement)
PE-4
Access Control for Transmission Medium
- ChapterNumber: TAILORING CRITERIA
- Source File: NIST_SP_800-171r2.pdf
- Coverage: AVAILABLE

### PE-5 (Requirement)
PE-5
Access Control for Output Devices
- ChapterNumber: TAILORING CRITERIA
- Source File: NIST_SP_800-171r2.pdf
- Coverage: AVAILABLE

### PE-6 (Requirement)
PE-6
Monitoring Physical Access
- ChapterNumber: TAILORING CRITERIA
- Source File: NIST_SP_800-171r2.pdf
- Coverage: AVAILABLE

### PE-6(1) (Requirement)
PE-6(1)
MONITORING PHYSICAL ACCESS | INTRUSION ALARMS / SURVEILLANCE EQUIPMENT
- ChapterNumber: TAILORING CRITERIA
- Source File: NIST_SP_800-171r2.pdf
- Coverage: AVAILABLE

### PE-8 (Requirement)
PE-8
Visitor Access Records
- ChapterNumber: TAILORING CRITERIA
- Source File: NIST_SP_800-171r2.pdf
- Coverage: AVAILABLE

### PE-9 (Requirement)
PE-9
Power Equipment and Cabling
- ChapterNumber: TAILORING CRITERIA
- Source File: NIST_SP_800-171r2.pdf
- Coverage: AVAILABLE

### PE-10 (Requirement)
PE-10
Emergency Shutoff
- ChapterNumber: TAILORING CRITERIA
- Source File: NIST_SP_800-171r2.pdf
- Coverage: AVAILABLE

### PE-11 (Requirement)
PE-11
Emergency Power
- ChapterNumber: TAILORING CRITERIA
- Source File: NIST_SP_800-171r2.pdf
- Coverage: AVAILABLE

### PE-12 (Requirement)
PE-12
Emergency Lighting
- ChapterNumber: TAILORING CRITERIA
- Source File: NIST_SP_800-171r2.pdf
- Coverage: AVAILABLE

### PE-13 (Requirement)
PE-13
Fire Protection
- ChapterNumber: TAILORING CRITERIA
- Source File: NIST_SP_800-171r2.pdf
- Coverage: AVAILABLE

### PE-13(3) (Requirement)
PE-13(3)
FIRE PROTECTION | AUTOMATIC FIRE SUPPRESSION
- ChapterNumber: TAILORING CRITERIA
- Source File: NIST_SP_800-171r2.pdf
- Coverage: AVAILABLE

### PE-14 (Requirement)
PE-14
Temperature and Humidity Controls
- ChapterNumber: TAILORING CRITERIA
- Source File: NIST_SP_800-171r2.pdf
- Coverage: AVAILABLE

### PE-15 (Requirement)
PE-15
Water Damage Protection
- ChapterNumber: TAILORING CRITERIA
- Source File: NIST_SP_800-171r2.pdf
- Coverage: AVAILABLE

### PE-16 (Requirement)
PE-16
Delivery and Removal
- ChapterNumber: TAILORING CRITERIA
- Source File: NIST_SP_800-171r2.pdf
- Coverage: AVAILABLE

### PE-17 (Requirement)
PE-17
Alternate Work Site
- ChapterNumber: TAILORING CRITERIA
- Source File: NIST_SP_800-171r2.pdf
- Coverage: AVAILABLE

### PL-1 (Requirement)
PL-1
Security Planning Policy and Procedures
- ChapterNumber: TAILORING CRITERIA
- Source File: NIST_SP_800-171r2.pdf
- Coverage: AVAILABLE

### PL-2 (Requirement)
PL-2
System Security Plan
- ChapterNumber: TAILORING CRITERIA
- Source File: NIST_SP_800-171r2.pdf
- Coverage: AVAILABLE

### PL-2(3) (Requirement)
PL-2(3)
SYSTEM SECURITY PLAN | PLAN / COORDINATE WITH OTHER ORGANIZATIONAL ENTITIES
- ChapterNumber: TAILORING CRITERIA
- Source File: NIST_SP_800-171r2.pdf
- Coverage: AVAILABLE

### PL-4 (Requirement)
PL-4
Rules of Behavior
- ChapterNumber: TAILORING CRITERIA
- Source File: NIST_SP_800-171r2.pdf
- Coverage: AVAILABLE

### PL-4(1) (Requirement)
PL-4(1)
RULES OF BEHAVIOR | SOCIAL MEDIA AND NETWORKING RESTRICTIONS
- ChapterNumber: TAILORING CRITERIA
- Source File: NIST_SP_800-171r2.pdf
- Coverage: AVAILABLE

### PL-8 (Requirement)
PL-8
Information Security Architecture
- ChapterNumber: TAILORING CRITERIA
- Source File: NIST_SP_800-171r2.pdf
- Coverage: AVAILABLE

### PS-1 (Requirement)
PS-1
Personnel Security Policy and Procedures
- ChapterNumber: TAILORING CRITERIA
- Source File: NIST_SP_800-171r2.pdf
- Coverage: AVAILABLE

### PS-2 (Requirement)
PS-2
Position Risk Designation
- ChapterNumber: TAILORING CRITERIA
- Source File: NIST_SP_800-171r2.pdf
- Coverage: AVAILABLE

### PS-3 (Requirement)
PS-3
Personnel Screening
- ChapterNumber: TAILORING CRITERIA
- Source File: NIST_SP_800-171r2.pdf
- Coverage: AVAILABLE

### PS-4 (Requirement)
PS-4
Personnel Termination
- ChapterNumber: TAILORING CRITERIA
- Source File: NIST_SP_800-171r2.pdf
- Coverage: AVAILABLE

### PS-5 (Requirement)
PS-5
Personnel Transfer
- ChapterNumber: TAILORING CRITERIA
- Source File: NIST_SP_800-171r2.pdf
- Coverage: AVAILABLE

### PS-6 (Requirement)
PS-6
Access Agreements
- ChapterNumber: TAILORING CRITERIA
- Source File: NIST_SP_800-171r2.pdf
- Coverage: AVAILABLE

### PS-7 (Requirement)
PS-7
Third-Party Personnel Security
- ChapterNumber: TAILORING CRITERIA
- Source File: NIST_SP_800-171r2.pdf
- Coverage: AVAILABLE

### PS-8 (Requirement)
PS-8
Personnel Sanctions
- ChapterNumber: TAILORING CRITERIA
- Source File: NIST_SP_800-171r2.pdf
- Coverage: AVAILABLE

### SA-1 (Requirement)
SA-1
System and Services Acquisition Policy and Procedures
- ChapterNumber: TAILORING CRITERIA
- Source File: NIST_SP_800-171r2.pdf
- Coverage: AVAILABLE

### SA-2 (Requirement)
SA-2
Allocation of Resources
- ChapterNumber: TAILORING CRITERIA
- Source File: NIST_SP_800-171r2.pdf
- Coverage: AVAILABLE

### SA-3 (Requirement)
SA-3
System Development Life Cycle
- ChapterNumber: TAILORING CRITERIA
- Source File: NIST_SP_800-171r2.pdf
- Coverage: AVAILABLE

### SA-4 (Requirement)
SA-4
Acquisition Process
- ChapterNumber: TAILORING CRITERIA
- Source File: NIST_SP_800-171r2.pdf
- Coverage: AVAILABLE

### SA-4(1) (Requirement)
SA-4(1)
ACQUISITION PROCESS | FUNCTIONAL PROPERTIES OF SECURITY CONTROLS
- ChapterNumber: TAILORING CRITERIA
- Source File: NIST_SP_800-171r2.pdf
- Coverage: AVAILABLE

### SA-4(2) (Requirement)
SA-4(2)
ACQUISITION PROCESS | DESIGN / IMPLEMENTATION INFORMATION FOR SECURITY CONTROLS
- ChapterNumber: TAILORING CRITERIA
- Source File: NIST_SP_800-171r2.pdf
- Coverage: AVAILABLE

### SA-4(9) (Requirement)
SA-4(9)
ACQUISITION PROCESS | FUNCTIONS / PORTS / PROTOCOLS / SERVICES IN USE
- ChapterNumber: TAILORING CRITERIA
- Source File: NIST_SP_800-171r2.pdf
- Coverage: AVAILABLE

### SA-4(10) (Requirement)
SA-4(10)
ACQUISITION PROCESS | USE OF APPROVED PIV PRODUCTS
- ChapterNumber: TAILORING CRITERIA
- Source File: NIST_SP_800-171r2.pdf
- Coverage: AVAILABLE

### SA-5 (Requirement)
SA-5
System Documentation
- ChapterNumber: TAILORING CRITERIA
- Source File: NIST_SP_800-171r2.pdf
- Coverage: AVAILABLE

### SA-8 (Requirement)
SA-8
Security Engineering Principles
- ChapterNumber: TAILORING CRITERIA
- Source File: NIST_SP_800-171r2.pdf
- Coverage: AVAILABLE

### SA-9 (Requirement)
SA-9
External System Services
- ChapterNumber: TAILORING CRITERIA
- Source File: NIST_SP_800-171r2.pdf
- Coverage: AVAILABLE

### SA-9(2) (Requirement)
SA-9(2)
EXTERNAL SYSTEMS | IDENTIFICATION OF FUNCTIONS / PORTS / PROTOCOLS / SERVICES
- ChapterNumber: TAILORING CRITERIA
- Source File: NIST_SP_800-171r2.pdf
- Coverage: AVAILABLE

### SA-10 (Requirement)
SA-10
Developer Configuration Management
- ChapterNumber: TAILORING CRITERIA
- Source File: NIST_SP_800-171r2.pdf
- Coverage: AVAILABLE

### SA-11 (Requirement)
SA-11
Developer Security Testing and Evaluation
- ChapterNumber: TAILORING CRITERIA
- Source File: NIST_SP_800-171r2.pdf
- Coverage: AVAILABLE

### SC-1 (Requirement)
SC-1
System and Communications Protection Policy and Procedures
- ChapterNumber: TAILORING CRITERIA
- Source File: NIST_SP_800-171r2.pdf
- Coverage: AVAILABLE

### SC-2 (Requirement)
SC-2
Application Partitioning
- ChapterNumber: TAILORING CRITERIA
- Source File: NIST_SP_800-171r2.pdf
- Coverage: AVAILABLE

### SC-4 (Requirement)
SC-4
Information in Shared Resources
- ChapterNumber: TAILORING CRITERIA
- Source File: NIST_SP_800-171r2.pdf
- Coverage: AVAILABLE

### SC-5 (Requirement)
SC-5
Denial of Service Protection
- ChapterNumber: TAILORING CRITERIA
- Source File: NIST_SP_800-171r2.pdf
- Coverage: AVAILABLE

### SC-7 (Requirement)
SC-7
Boundary Protection
- ChapterNumber: TAILORING CRITERIA
- Source File: NIST_SP_800-171r2.pdf
- Coverage: AVAILABLE

### SC-7(3) (Requirement)
SC-7(3)
BOUNDARY PROTECTION | ACCESS POINTS
- ChapterNumber: TAILORING CRITERIA
- Source File: NIST_SP_800-171r2.pdf
- Coverage: AVAILABLE

### SC-7(4) (Requirement)
SC-7(4)
BOUNDARY PROTECTION | EXTERNAL TELECOMMUNICATIONS SERVICES
- ChapterNumber: TAILORING CRITERIA
- Source File: NIST_SP_800-171r2.pdf
- Coverage: AVAILABLE

### SC-7(5) (Requirement)
SC-7(5)
BOUNDARY PROTECTION | DENY BY DEFAULT / ALLOW BY EXCEPTION
- ChapterNumber: TAILORING CRITERIA
- Source File: NIST_SP_800-171r2.pdf
- Coverage: AVAILABLE

### SC-7(7) (Requirement)
SC-7(7)
BOUNDARY PROTECTION | PREVENT SPLIT TUNNELING FOR REMOTE DEVICES
- ChapterNumber: TAILORING CRITERIA
- Source File: NIST_SP_800-171r2.pdf
- Coverage: AVAILABLE

### SC-8 (Requirement)
SC-8
Transmission Confidentiality and Integrity
- ChapterNumber: TAILORING CRITERIA
- Source File: NIST_SP_800-171r2.pdf
- Coverage: AVAILABLE

### SC-8(1) (Requirement)
SC-8(1)
TRANSMISSION CONFIDENTIALITY AND INTEGRITY | CRYPTOGRAPHIC OR ALTERNATE PHYSICAL PROTECTION
- ChapterNumber: TAILORING CRITERIA
- Source File: NIST_SP_800-171r2.pdf
- Coverage: AVAILABLE

### SC-10 (Requirement)
SC-10
Network Disconnect
- ChapterNumber: TAILORING CRITERIA
- Source File: NIST_SP_800-171r2.pdf
- Coverage: AVAILABLE

### SC-12 (Requirement)
SC-12
Cryptographic Key Establishment and Management
- ChapterNumber: TAILORING CRITERIA
- Source File: NIST_SP_800-171r2.pdf
- Coverage: AVAILABLE

### SC-13 (Requirement)
SC-13
Cryptographic Protection
- ChapterNumber: TAILORING CRITERIA
- Source File: NIST_SP_800-171r2.pdf
- Coverage: AVAILABLE

### SC-15 (Requirement)
SC-15
Collaborative Computing Devices
- ChapterNumber: TAILORING CRITERIA
- Source File: NIST_SP_800-171r2.pdf
- Coverage: AVAILABLE

### SC-17 (Requirement)
SC-17
Public Key Infrastructure Certificates
- ChapterNumber: TAILORING CRITERIA
- Source File: NIST_SP_800-171r2.pdf
- Coverage: AVAILABLE

### SC-18 (Requirement)
SC-18
Mobile Code
- ChapterNumber: TAILORING CRITERIA
- Source File: NIST_SP_800-171r2.pdf
- Coverage: AVAILABLE

### SC-19 (Requirement)
SC-19
Voice over Internet Protocol
- ChapterNumber: TAILORING CRITERIA
- Source File: NIST_SP_800-171r2.pdf
- Coverage: AVAILABLE

### SC-20 (Requirement)
SC-20
Secure Name /Address Resolution Service (Authoritative Source)
- ChapterNumber: TAILORING CRITERIA
- Source File: NIST_SP_800-171r2.pdf
- Coverage: AVAILABLE

### SC-21 (Requirement)
SC-21
Secure Name /Address Resolution Service (Recursive or Caching Resolver)
- ChapterNumber: TAILORING CRITERIA
- Source File: NIST_SP_800-171r2.pdf
- Coverage: AVAILABLE

### SC-22 (Requirement)
SC-22
Architecture and Provisioning for Name/Address Resolution Service
- ChapterNumber: TAILORING CRITERIA
- Source File: NIST_SP_800-171r2.pdf
- Coverage: AVAILABLE

### SC-23 (Requirement)
SC-23
Session Authenticity
- ChapterNumber: TAILORING CRITERIA
- Source File: NIST_SP_800-171r2.pdf
- Coverage: AVAILABLE

### SC-28 (Requirement)
SC-28
Protection of Information at Rest
- ChapterNumber: TAILORING CRITERIA
- Source File: NIST_SP_800-171r2.pdf
- Coverage: AVAILABLE

### SC-39 (Requirement)
SC-39
Process Isolation
- ChapterNumber: TAILORING CRITERIA
- Source File: NIST_SP_800-171r2.pdf
- Coverage: AVAILABLE

### SI-1 (Requirement)
SI-1
System and Information Integrity Policy and Procedures
- ChapterNumber: TAILORING CRITERIA
- Source File: NIST_SP_800-171r2.pdf
- Coverage: AVAILABLE

### SI-2 (Requirement)
SI-2
Flaw Remediation
- ChapterNumber: TAILORING CRITERIA
- Source File: NIST_SP_800-171r2.pdf
- Coverage: AVAILABLE

### SI-2(2) (Requirement)
SI-2(2)
FLAW REMEDIATION | AUTOMATED FLAW REMEDIATION STATUS
- ChapterNumber: TAILORING CRITERIA
- Source File: NIST_SP_800-171r2.pdf
- Coverage: AVAILABLE

### SI-3 (Requirement)
SI-3
Malicious Code Protection
- ChapterNumber: TAILORING CRITERIA
- Source File: NIST_SP_800-171r2.pdf
- Coverage: AVAILABLE

### SI-3(1) (Requirement)
SI-3(1)
MALICIOUS CODE PROTECTION | CENTRAL MANAGEMENT
- ChapterNumber: TAILORING CRITERIA
- Source File: NIST_SP_800-171r2.pdf
- Coverage: AVAILABLE

### SI-3(2) (Requirement)
SI-3(2)
MALICIOUS CODE PROTECTION | AUTOMATIC UPDATES
- ChapterNumber: TAILORING CRITERIA
- Source File: NIST_SP_800-171r2.pdf
- Coverage: AVAILABLE

### SI-4 (Requirement)
SI-4
System Monitoring
- ChapterNumber: TAILORING CRITERIA
- Source File: NIST_SP_800-171r2.pdf
- Coverage: AVAILABLE

### SI-4(2) (Requirement)
SI-4(2)
SYSTEM MONITORING | AUTOMATED TOOLS FOR REAL-TIME ANALYSIS
- ChapterNumber: TAILORING CRITERIA
- Source File: NIST_SP_800-171r2.pdf
- Coverage: AVAILABLE

### SI-4(4) (Requirement)
SI-4(4)
SYSTEM MONITORING | INBOUND AND OUTBOUND COMMUNICATIONS TRAFFIC
- ChapterNumber: TAILORING CRITERIA
- Source File: NIST_SP_800-171r2.pdf
- Coverage: AVAILABLE

### SI-4(5) (Requirement)
SI-4(5)
SYSTEM MONITORING | SYSTEM-GENERATED ALERTS
- ChapterNumber: TAILORING CRITERIA
- Source File: NIST_SP_800-171r2.pdf
- Coverage: AVAILABLE

### SI-5 (Requirement)
SI-5
Security Alerts, Advisories, and Directives
- ChapterNumber: TAILORING CRITERIA
- Source File: NIST_SP_800-171r2.pdf
- Coverage: AVAILABLE

### SI-7 (Requirement)
SI-7
Software, Firmware, and Information Integrity
- ChapterNumber: TAILORING CRITERIA
- Source File: NIST_SP_800-171r2.pdf
- Coverage: AVAILABLE

### SI-7(1) (Requirement)
SI-7(1)
SOFTWARE, FIRMWARE, AND INFORMATION INTEGRITY | INTEGRITY CHECKS
- ChapterNumber: TAILORING CRITERIA
- Source File: NIST_SP_800-171r2.pdf
- Coverage: AVAILABLE

### SI-7(7) (Requirement)
SI-7(7)
SOFTWARE, FIRMWARE, AND INFORMATION INTEGRITY | INTEGRATION OF DETECTION AND RESPONSE
- ChapterNumber: TAILORING CRITERIA
- Source File: NIST_SP_800-171r2.pdf
- Coverage: AVAILABLE

### SI-8 (Requirement)
SI-8
Spam Protection
- ChapterNumber: TAILORING CRITERIA
- Source File: NIST_SP_800-171r2.pdf
- Coverage: AVAILABLE

### SI-8(1) (Requirement)
SI-8(1)
SPAM PROTECTION | CENTRAL MANAGEMENT
- ChapterNumber: TAILORING CRITERIA
- Source File: NIST_SP_800-171r2.pdf
- Coverage: AVAILABLE

### SI-8(2) (Requirement)
SI-8(2)
SPAM PROTECTION | AUTOMATIC UPDATES
- ChapterNumber: TAILORING CRITERIA
- Source File: NIST_SP_800-171r2.pdf
- Coverage: AVAILABLE

### SI-10 (Requirement)
SI-10
Information Input Validation
- ChapterNumber: TAILORING CRITERIA
- Source File: NIST_SP_800-171r2.pdf
- Coverage: AVAILABLE

### SI-11 (Requirement)
SI-11
Error Handling
- ChapterNumber: TAILORING CRITERIA
- Source File: NIST_SP_800-171r2.pdf
- Coverage: AVAILABLE

### SI-12 (Requirement)
SI-12
Information Handling and Retention
- ChapterNumber: TAILORING CRITERIA
- Source File: NIST_SP_800-171r2.pdf
- Coverage: AVAILABLE

### SI-16 (Requirement)
SI-16
Memory Protection
- ChapterNumber: TAILORING CRITERIA
- Source File: NIST_SP_800-171r2.pdf
- Coverage: AVAILABLE

### NCO (Requirement)
NCO
NOT DIRECTLY RELATED TO PROTECTING THE CONFIDENTIALITY OF CUI.
- ChapterNumber: TAILORING CRITERIA
- Source File: NIST_SP_800-171r2.pdf
- Coverage: AVAILABLE

### FED (Requirement)
FED
UNIQUELY FEDERAL, PRIMARILY THE RESPONSIBILITY OF THE FEDERAL GOVERNMENT.
- ChapterNumber: TAILORING CRITERIA
- Source File: NIST_SP_800-171r2.pdf
- Coverage: AVAILABLE

### NFO (Requirement)
NFO
EXPECTED TO BE ROUTINELY SATISFIED BY NONFEDERAL ORGANIZATIONS WITHOUT SPECIFICATION.
- ChapterNumber: TAILORING CRITERIA
- Source File: NIST_SP_800-171r2.pdf
- Coverage: AVAILABLE

### CUI (Requirement)
CUI
THE CUI BASIC OR DERIVED SECURITY REQUIREMENT IS REFLECTED IN AND IS TRACEABLE TO THE SECURITY CONTROL, CONTROL ENHANCEMENT, OR SPECIFIC ELEMENTS OF THE CONTROL/ENHANCEMENT.
- ChapterNumber: TAILORING CRITERIA
- Source File: NIST_SP_800-171r2.pdf
- Coverage: AVAILABLE

## R17: TABLE E-1: TAILORING ACTIONS FOR ACCESS CONTROLS (Info)
- Level: 2

### AC-1 (Requirement)
AC-1
Access Control Policy and Procedures
- ChapterNumber: TABLE E-1:  TAILORING ACTIONS FOR ACCESS CONTROLS
- Source File: NIST_SP_800-171r2.pdf
- Coverage: AVAILABLE

### AC-2 (Requirement)
AC-2
Account Management
- ChapterNumber: TABLE E-1:  TAILORING ACTIONS FOR ACCESS CONTROLS
- Source File: NIST_SP_800-171r2.pdf
- Coverage: AVAILABLE

### AC-2(1) (Requirement)
AC-2(1)
ACCOUNT MANAGEMENT | AUTOMATED SYSTEM ACCOUNT MANAGEMENT
- ChapterNumber: TABLE E-1:  TAILORING ACTIONS FOR ACCESS CONTROLS
- Source File: NIST_SP_800-171r2.pdf
- Coverage: AVAILABLE

### AC-2(2) (Requirement)
AC-2(2)
ACCOUNT MANAGEMENT | REMOVAL OF TEMPORARY / EMERGENCY ACCOUNTS
- ChapterNumber: TABLE E-1:  TAILORING ACTIONS FOR ACCESS CONTROLS
- Source File: NIST_SP_800-171r2.pdf
- Coverage: AVAILABLE

### AC-2(3) (Requirement)
AC-2(3)
ACCOUNT MANAGEMENT | DISABLE INACTIVE ACCOUNTS
- ChapterNumber: TABLE E-1:  TAILORING ACTIONS FOR ACCESS CONTROLS
- Source File: NIST_SP_800-171r2.pdf
- Coverage: AVAILABLE

### AC-2(4) (Requirement)
AC-2(4)
ACCOUNT MANAGEMENT | AUTOMATED AUDIT ACTIONS
- ChapterNumber: TABLE E-1:  TAILORING ACTIONS FOR ACCESS CONTROLS
- Source File: NIST_SP_800-171r2.pdf
- Coverage: AVAILABLE

### AC-3 (Requirement)
AC-3
Access Enforcement
- ChapterNumber: TABLE E-1:  TAILORING ACTIONS FOR ACCESS CONTROLS
- Source File: NIST_SP_800-171r2.pdf
- Coverage: AVAILABLE

### AC-4 (Requirement)
AC-4
Information Flow Enforcement
- ChapterNumber: TABLE E-1:  TAILORING ACTIONS FOR ACCESS CONTROLS
- Source File: NIST_SP_800-171r2.pdf
- Coverage: AVAILABLE

### AC-5 (Requirement)
AC-5
Separation of Duties
- ChapterNumber: TABLE E-1:  TAILORING ACTIONS FOR ACCESS CONTROLS
- Source File: NIST_SP_800-171r2.pdf
- Coverage: AVAILABLE

### AC-6 (Requirement)
AC-6
Least Privilege
- ChapterNumber: TABLE E-1:  TAILORING ACTIONS FOR ACCESS CONTROLS
- Source File: NIST_SP_800-171r2.pdf
- Coverage: AVAILABLE

### AC-6(1) (Requirement)
AC-6(1)
LEAST PRIVILEGE | AUTHORIZE ACCESS TO SECURITY FUNCTIONS
- ChapterNumber: TABLE E-1:  TAILORING ACTIONS FOR ACCESS CONTROLS
- Source File: NIST_SP_800-171r2.pdf
- Coverage: AVAILABLE

### AC-6(2) (Requirement)
AC-6(2)
LEAST PRIVILEGE | NON-PRIVILEGED ACCESS FOR NONSECURITY FUNCTIONS
- ChapterNumber: TABLE E-1:  TAILORING ACTIONS FOR ACCESS CONTROLS
- Source File: NIST_SP_800-171r2.pdf
- Coverage: AVAILABLE

### AC-6(5) (Requirement)
AC-6(5)
LEAST PRIVILEGE | PRIVILEGED ACCOUNTS
- ChapterNumber: TABLE E-1:  TAILORING ACTIONS FOR ACCESS CONTROLS
- Source File: NIST_SP_800-171r2.pdf
- Coverage: AVAILABLE

### AC-6(9) (Requirement)
AC-6(9)
LEAST PRIVILEGE | AUDITING USE OF PRIVILEGED FUNCTIONS
- ChapterNumber: TABLE E-1:  TAILORING ACTIONS FOR ACCESS CONTROLS
- Source File: NIST_SP_800-171r2.pdf
- Coverage: AVAILABLE

### AC-6(10) (Requirement)
AC-6(10)
LEAST PRIVILEGE | PROHIBIT NON-PRIVILEGED USERS FROM EXECUTING PRIVILEGED FUNCTIONS
- ChapterNumber: TABLE E-1:  TAILORING ACTIONS FOR ACCESS CONTROLS
- Source File: NIST_SP_800-171r2.pdf
- Coverage: AVAILABLE

### AC-7 (Requirement)
AC-7
Unsuccessful Logon Attempts
- ChapterNumber: TABLE E-1:  TAILORING ACTIONS FOR ACCESS CONTROLS
- Source File: NIST_SP_800-171r2.pdf
- Coverage: AVAILABLE

### AC-8 (Requirement)
AC-8
System Use Notification
- ChapterNumber: TABLE E-1:  TAILORING ACTIONS FOR ACCESS CONTROLS
- Source File: NIST_SP_800-171r2.pdf
- Coverage: AVAILABLE

### AC-11 (Requirement)
AC-11
Session Lock
- ChapterNumber: TABLE E-1:  TAILORING ACTIONS FOR ACCESS CONTROLS
- Source File: NIST_SP_800-171r2.pdf
- Coverage: AVAILABLE

### AC-11(1) (Requirement)
AC-11(1)
SESSION LOCK | PATTERN-HIDING DISPLAYS
- ChapterNumber: TABLE E-1:  TAILORING ACTIONS FOR ACCESS CONTROLS
- Source File: NIST_SP_800-171r2.pdf
- Coverage: AVAILABLE

### AC-12 (Requirement)
AC-12
Session Termination
- ChapterNumber: TABLE E-1:  TAILORING ACTIONS FOR ACCESS CONTROLS
- Source File: NIST_SP_800-171r2.pdf
- Coverage: AVAILABLE

### AC-14 (Requirement)
AC-14
Permitted Actions without Identification or Authentication
- ChapterNumber: TABLE E-1:  TAILORING ACTIONS FOR ACCESS CONTROLS
- Source File: NIST_SP_800-171r2.pdf
- Coverage: AVAILABLE

### AC-17 (Requirement)
AC-17
Remote Access
- ChapterNumber: TABLE E-1:  TAILORING ACTIONS FOR ACCESS CONTROLS
- Source File: NIST_SP_800-171r2.pdf
- Coverage: AVAILABLE

### AC-17(1) (Requirement)
AC-17(1)
REMOTE ACCESS | AUTOMATED MONITORING / CONTROL
- ChapterNumber: TABLE E-1:  TAILORING ACTIONS FOR ACCESS CONTROLS
- Source File: NIST_SP_800-171r2.pdf
- Coverage: AVAILABLE

### AC-17(2) (Requirement)
AC-17(2)
REMOTE ACCESS | PROTECTION OF CONFIDENTIALITY / INTEGRITY USING ENCRYPTION
- ChapterNumber: TABLE E-1:  TAILORING ACTIONS FOR ACCESS CONTROLS
- Source File: NIST_SP_800-171r2.pdf
- Coverage: AVAILABLE

### AC-17(3) (Requirement)
AC-17(3)
REMOTE ACCESS | MANAGED ACCESS CONTROL POINTS
- ChapterNumber: TABLE E-1:  TAILORING ACTIONS FOR ACCESS CONTROLS
- Source File: NIST_SP_800-171r2.pdf
- Coverage: AVAILABLE

### AC-17(4) (Requirement)
AC-17(4)
REMOTE ACCESS | PRIVILEGED COMMANDS / ACCESS
- ChapterNumber: TABLE E-1:  TAILORING ACTIONS FOR ACCESS CONTROLS
- Source File: NIST_SP_800-171r2.pdf
- Coverage: AVAILABLE

### AC-18 (Requirement)
AC-18
Wireless Access
- ChapterNumber: TABLE E-1:  TAILORING ACTIONS FOR ACCESS CONTROLS
- Source File: NIST_SP_800-171r2.pdf
- Coverage: AVAILABLE

### AC-18(1) (Requirement)
AC-18(1)
WIRELESS ACCESS | AUTHENTICATION AND ENCRYPTION
- ChapterNumber: TABLE E-1:  TAILORING ACTIONS FOR ACCESS CONTROLS
- Source File: NIST_SP_800-171r2.pdf
- Coverage: AVAILABLE

### AC-19 (Requirement)
AC-19
Access Control for Mobile Devices
- ChapterNumber: TABLE E-1:  TAILORING ACTIONS FOR ACCESS CONTROLS
- Source File: NIST_SP_800-171r2.pdf
- Coverage: AVAILABLE

### AC-19(5) (Requirement)
AC-19(5)
ACCESS CONTROL FOR MOBILE DEVICES | FULL DEVICE / CONTAINER-BASED ENCRYPTION
- ChapterNumber: TABLE E-1:  TAILORING ACTIONS FOR ACCESS CONTROLS
- Source File: NIST_SP_800-171r2.pdf
- Coverage: AVAILABLE

### AC-20 (Requirement)
AC-20
Use of External Systems
- ChapterNumber: TABLE E-1:  TAILORING ACTIONS FOR ACCESS CONTROLS
- Source File: NIST_SP_800-171r2.pdf
- Coverage: AVAILABLE

### AC-20(1) (Requirement)
AC-20(1)
USE OF EXTERNAL SYSTEMS | LIMITS ON AUTHORIZED USE
- ChapterNumber: TABLE E-1:  TAILORING ACTIONS FOR ACCESS CONTROLS
- Source File: NIST_SP_800-171r2.pdf
- Coverage: AVAILABLE

### AC-20(2) (Requirement)
AC-20(2)
USE OF EXTERNAL SYSTEMS | PORTABLE STORAGE DEVICES
- ChapterNumber: TABLE E-1:  TAILORING ACTIONS FOR ACCESS CONTROLS
- Source File: NIST_SP_800-171r2.pdf
- Coverage: AVAILABLE

### AC-21 (Requirement)
AC-21
Information Sharing
- ChapterNumber: TABLE E-1:  TAILORING ACTIONS FOR ACCESS CONTROLS
- Source File: NIST_SP_800-171r2.pdf
- Coverage: AVAILABLE

### AC-22 (Requirement)
AC-22
Publicly Accessible Content
- ChapterNumber: TABLE E-1:  TAILORING ACTIONS FOR ACCESS CONTROLS
- Source File: NIST_SP_800-171r2.pdf
- Coverage: AVAILABLE

## R18: TABLE E-14: TAILORING ACTIONS FOR RISK ASSESSMENT CONTROLS (Info)
- Level: 2

### RA-1 (Requirement)
RA-1
Risk Assessment Policy and Procedures
- ChapterNumber: TABLE E-14:  TAILORING ACTIONS FOR RISK ASSESSMENT CONTROLS
- Source File: NIST_SP_800-171r2.pdf
- Coverage: AVAILABLE

### RA-2 (Requirement)
RA-2
Security Categorization
- ChapterNumber: TABLE E-14:  TAILORING ACTIONS FOR RISK ASSESSMENT CONTROLS
- Source File: NIST_SP_800-171r2.pdf
- Coverage: AVAILABLE

### RA-5 (Requirement)
RA-5
Vulnerability Scanning
- ChapterNumber: TABLE E-14:  TAILORING ACTIONS FOR RISK ASSESSMENT CONTROLS
- Source File: NIST_SP_800-171r2.pdf
- Coverage: AVAILABLE

### RA-5(1) (Requirement)
RA-5(1)
VULNERABILITY SCANNING | UPDATE TOOL CAPABILITY
- ChapterNumber: TABLE E-14:  TAILORING ACTIONS FOR RISK ASSESSMENT CONTROLS
- Source File: NIST_SP_800-171r2.pdf
- Coverage: AVAILABLE

### RA-5(2) (Requirement)
RA-5(2)
VULNERABILITY SCANNING | UPDATE BY FREQUENCY / PRIOR TO NEW SCAN / WHEN IDENTIFIED
- ChapterNumber: TABLE E-14:  TAILORING ACTIONS FOR RISK ASSESSMENT CONTROLS
- Source File: NIST_SP_800-171r2.pdf
- Coverage: AVAILABLE

### RA-5(5) (Requirement)
RA-5(5)
VULNERABILITY SCANNING | PRIVILEGED ACCESS
- ChapterNumber: TABLE E-14:  TAILORING ACTIONS FOR RISK ASSESSMENT CONTROLS
- Source File: NIST_SP_800-171r2.pdf
- Coverage: AVAILABLE
